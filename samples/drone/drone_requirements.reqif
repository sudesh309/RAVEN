# Drone System Requirements Specification
Drone System Requirements Specification — 4-level hierarchy generated by reqgraph

# Specification: Drone System Requirements Specification

## DRONE-SYS-001
- ReqText: The drone system shall perform autonomous aerial operations including take-off, waypoint navigation, mission execution, and landing without continuous human intervention.
- Rationale: Enables unmanned inspection and survey missions.
- Level: Level-1
- Derives -> DRONE-FC-001
- Derives -> DRONE-FC-002
- Derives -> DRONE-FC-003

### DRONE-FC-001
- ReqText: The flight control subsystem shall stabilise the drone attitude to within ±2° of setpoint in all axes under Beaufort-3 wind conditions.
- Rationale: Stable platform required for consistent sensor data.
- Level: Level-2
- Derives -> DRONE-MOT-001
- Derives -> DRONE-MOT-002
- Derives -> DRONE-MOT-003

#### DRONE-MOT-001
- ReqText: Each brushless motor shall produce a minimum static thrust of 500 g at 100% throttle at standard atmospheric conditions (ISA sea level).
- Rationale: Thrust-to-weight ratio ≥ 2:1 at MTOW of 1 kg.
- Level: Level-3
- Derives -> DRONE-ATT-001
- Derives -> DRONE-ATT-002
- Derives -> DRONE-ATT-003

##### DRONE-ATT-001
- ReqText: The attitude controller shall implement a cascaded PID architecture with inner rate loop and outer angle loop, augmented with feed-forward compensation derived from the vehicle inertia model.
- Rationale: Feed-forward reduces control effort and improves transient response.
- Level: Level-4

##### DRONE-ATT-002
- ReqText: The roll and pitch rate control loop shall achieve a closed-loop bandwidth of at least 15 Hz with a phase margin of at least 45°.
- Rationale: Stability and disturbance rejection specifications.
- Level: Level-4

##### DRONE-ATT-003
- ReqText: The attitude estimator shall fuse IMU, magnetometer, and barometer data using an Extended Kalman Filter with a prediction step at IMU rate and update steps at sensor rates.
- Rationale: Robust attitude estimation under vibration and magnetic interference.
- Level: Level-4

#### DRONE-MOT-002
- ReqText: Each Electronic Speed Controller (ESC) shall respond to a throttle command change from 0% to 100% within 5 ms.
- Rationale: Attitude loop bandwidth requires fast actuator response.
- Level: Level-3

#### DRONE-MOT-003
- ReqText: Motors and ESCs shall operate within a temperature range of 0 °C to 60 °C without derating or protective shutdown.
- Rationale: Operational environment envelope for typical outdoor use.
- Level: Level-3

### DRONE-FC-002
- ReqText: The flight control subsystem shall execute GPS waypoint navigation with a cross-track error not exceeding 2 m.
- Rationale: Mission path accuracy for geospatial data collection.
- Level: Level-2

### DRONE-FC-003
- ReqText: The flight control subsystem shall support fully autonomous take-off and precision landing within 1 m of the designated landing point.
- Rationale: Reduces operator workload; enables one-person operations.
- Level: Level-2

## DRONE-SYS-002
- ReqText: The drone system shall operate safely within defined airspace constraints, including altitude limits, geofencing, and mandatory failsafe responses.
- Rationale: Compliance with aviation regulations and operator safety.
- Level: Level-1
- Derives -> DRONE-PWR-001
- Derives -> DRONE-PWR-002
- Derives -> DRONE-PWR-003

### DRONE-PWR-001
- ReqText: The power system shall supply a nominal bus voltage of 25.2 V ±5% to all propulsion and avionics consumers throughout the full discharge cycle.
- Rationale: ESC and avionics operating range compliance.
- Level: Level-2
- Derives -> DRONE-BAT-001
- Derives -> DRONE-BAT-002
- Derives -> DRONE-BAT-003

#### DRONE-BAT-001
- ReqText: The battery pack shall store a minimum usable energy of 22 Wh (6S LiPo, 5000 mAh) to support the 30-minute endurance requirement.
- Rationale: Energy budget derived from hover power consumption model.
- Level: Level-3
- Derives -> DRONE-FSF-001
- Derives -> DRONE-FSF-002
- Derives -> DRONE-FSF-003

##### DRONE-FSF-001
- ReqText: The flight controller shall enter hover mode and activate the return-to- home sequence within 2 s of detecting a continuous RC link loss.
- Rationale: Prevents flyaway on intermittent signal loss during manual flight.
- Level: Level-4

##### DRONE-FSF-002
- ReqText: The system shall initiate a return-to-home manoeuvre automatically when battery SoC falls below 15%, overriding any current waypoint mission.
- Rationale: Ensures the drone returns before the low-battery auto-land threshold.
- Level: Level-4

##### DRONE-FSF-003
- ReqText: The system shall initiate an immediate auto-land sequence at the current position when battery SoC falls below 5%, regardless of position.
- Rationale: Last-resort protection against total power loss.
- Level: Level-4

#### DRONE-BAT-002
- ReqText: The battery pack shall support a minimum of 200 full charge-discharge cycles before capacity degradation exceeds 20% of initial rating.
- Rationale: Battery service life for economic viability.
- Level: Level-3

#### DRONE-BAT-003
- ReqText: The battery management system (BMS) shall prevent overcharge above 4.2 V per cell and over-discharge below 3.0 V per cell.
- Rationale: Lithium cell safety and longevity.
- Level: Level-3

### DRONE-PWR-002
- ReqText: The power system shall continuously monitor battery state-of-charge (SoC) with an accuracy of ±3% and report it to the flight controller at 1 Hz.
- Rationale: Input to failsafe and mission planning logic.
- Level: Level-2

### DRONE-PWR-003
- ReqText: The power system shall trigger a return-to-home event when battery SoC falls below 20% and an immediate auto-land when SoC falls below 5%.
- Rationale: Prevents battery over-discharge and loss of vehicle.
- Level: Level-2

## DRONE-SYS-003
- ReqText: The drone system shall provide real-time bidirectional telemetry and command communication with a ground control station at a range of at least 1 km.
- Rationale: Situational awareness and in-flight override capability.
- Level: Level-1
- Derives -> DRONE-COM-001
- Derives -> DRONE-COM-002
- Derives -> DRONE-COM-003

### DRONE-COM-001
- ReqText: The communication subsystem shall maintain an RC control link with ≤ 20 ms round-trip latency at ranges up to 1 km in open terrain.
- Rationale: Pilot override responsiveness.
- Level: Level-2
- Derives -> DRONE-PLD-001
- Derives -> DRONE-PLD-002
- Derives -> DRONE-PLD-003

#### DRONE-PLD-001
- ReqText: The payload interface shall accept payloads of up to 500 g total mass and provide a regulated 12 V / 2 A power feed to the payload.
- Rationale: Supports standard inspection camera payload class.
- Level: Level-3
- Derives -> DRONE-PVF-001
- Derives -> DRONE-PVF-002
- Derives -> DRONE-PVF-003

##### DRONE-PVF-001
- ReqText: The drone shall demonstrate stable hover at 10 m AGL for 5 continuous minutes in Beaufort-3 (5.5 m/s) winds with position drift ≤ 1.5 m from home point.
- Rationale: Validates attitude control and GPS hold in realistic field conditions.
- Level: Level-4

##### DRONE-PVF-002
- ReqText: The drone shall complete a 10-waypoint rectangular survey route covering a 100 m × 50 m area at 20 m AGL with a cross-track deviation ≤ 2 m on each segment, as recorded by the onboard GPS log.
- Rationale: Validates waypoint navigation accuracy for survey missions.
- Level: Level-4

##### DRONE-PVF-003
- ReqText: The drone shall execute an autonomous precision landing and touch down within a 1 m radius circle centred on the designated landing marker under calm wind conditions (Beaufort ≤ 2).
- Rationale: Validates precision landing capability for confined deployment sites.
- Level: Level-4

#### DRONE-PLD-002
- ReqText: The integrated camera shall capture 4 K video at 30 fps with a minimum horizontal field of view of 84°.
- Rationale: Resolution and coverage for infrastructure inspection.
- Level: Level-3

#### DRONE-PLD-003
- ReqText: The 3-axis gimbal shall stabilise the camera to within ±0.01° of commanded pointing angle during normal flight manoeuvres.
- Rationale: Image quality and geo-referencing accuracy.
- Level: Level-3

### DRONE-COM-002
- ReqText: The communication subsystem shall transmit a MAVLink 2.0 telemetry stream at 10 Hz containing GPS position, attitude, battery SoC, and current flight mode.
- Rationale: Ground-station situational awareness.
- Level: Level-2

### DRONE-COM-003
- ReqText: The communication subsystem shall encrypt the command uplink channel using AES-128 to prevent unauthorised command injection.
- Rationale: Security against adversarial interference.
- Level: Level-2

## DRONE-SYS-004
- ReqText: The drone system shall achieve a minimum endurance of 30 minutes of continuous hover flight at maximum rated payload capacity.
- Rationale: Sufficient mission duration for typical inspection tasks.
- Level: Level-1
- Derives -> DRONE-NAV-001
- Derives -> DRONE-NAV-002
- Derives -> DRONE-NAV-003

### DRONE-NAV-001
- ReqText: The navigation subsystem shall provide a position solution with CEP ≤ 1.5 m under open-sky dual-band GNSS conditions.
- Rationale: Required for waypoint accuracy and precision landing.
- Level: Level-2
- Derives -> DRONE-SNS-001
- Derives -> DRONE-SNS-002
- Derives -> DRONE-SNS-003

#### DRONE-SNS-001
- ReqText: The inertial measurement unit (IMU) shall sample acceleration and angular rate at a minimum of 400 Hz on all six axes.
- Rationale: Minimum bandwidth for attitude control loop stability.
- Level: Level-3
- Derives -> DRONE-CPR-001
- Derives -> DRONE-CPR-002
- Derives -> DRONE-CPR-003

##### DRONE-CPR-001
- ReqText: The ground data link shall implement the MAVLink 2.0 protocol with message signing enabled; the dialect shall include HEARTBEAT, GLOBAL_POSITION_INT, ATTITUDE, SYS_STATUS, and BATTERY_STATUS messages.
- Rationale: Interoperability with standard GCS software (QGroundControl, Mission Planner).
- Level: Level-4

##### DRONE-CPR-002
- ReqText: The telemetry stream shall be transmitted on the 915 MHz band at a minimum data rate of 57.6 kbps and shall achieve a link budget margin of at least 6 dB at 1000 m slant range.
- Rationale: Ensures reliable downlink with multipath and atmospheric margin.
- Level: Level-4

##### DRONE-CPR-003
- ReqText: The command uplink shall encrypt all payload bytes using AES-128 in CBC mode with a session key derived from a pre-shared key via HKDF-SHA256; a new session key shall be generated on every power-on.
- Rationale: Prevents replay attacks and command injection.
- Level: Level-4

#### DRONE-SNS-002
- ReqText: The GNSS receiver shall acquire an initial position fix within 30 s from a cold start and within 5 s from a warm start.
- Rationale: Limits pre-flight wait time during field operations.
- Level: Level-3

#### DRONE-SNS-003
- ReqText: The barometric pressure sensor shall provide altitude estimates with an accuracy of ±0.5 m under static conditions.
- Rationale: Altitude hold and terrain-following accuracy.
- Level: Level-3

### DRONE-NAV-002
- ReqText: The navigation subsystem shall detect obstacles within a 5 m radius and reroute or halt the drone before a potential collision.
- Rationale: Prevents collisions with uncharted objects.
- Level: Level-2

### DRONE-NAV-003
- ReqText: The navigation subsystem shall enforce a configurable geofence boundary; the drone shall not exit the boundary under autonomous control.
- Rationale: Regulatory compliance and operator-defined exclusion zones.
- Level: Level-2
